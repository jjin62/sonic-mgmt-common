module sonic-otdr {
	namespace "http://github.com/Azure/sonic-otdr";
	prefix "sotdr";

	organization
		"SONiC";

	contact
		"SONiC";

	description
		"SONIC OTDR";

	revision 2023-11-24 {
		description
			"Initial revision.";
	}

  // extension statements

  // feature statements

  // identity statements

  // typedef statements
  typedef otdr-scan-type {
    description
      "A set of otdr scan configuration.";
    type enumeration {
      enum customized {
        description
          "use customized config per port.";
      }
      enum short {
        description
          "Short(2-5Km): use short common config.";
      }
      enum medium {
        description
          "Medium(5-60Km): use mediam common config";
      }
      enum long {
        description
          "Long(60-128Km): use long common config.";
      }
      enum auto {
        description
          "No config/range needed, otdr moudle scan in auto mode.";
      }
    }
  }

  typedef otdr-event-type {
    type enumeration {
      enum "unknown" {
        description
          "The event type is unknown";
      }
      enum non-reflective {
        description
          "The reflection suddenly decreased, displayed as a trace drop.";
      }
      enum reflective {
        description
          "The pulse reflect back to OTDR, displayed as a trace peak.";
      }
      enum fiber-end {
        description
          "Fiber end event.";
      }
    }
  }

  typedef fiber-type-profile {
    type enumeration {
      enum DSF {
        description
          "Dispersion shifted fiber";
      }
      enum LEAF {
        description
          "Large effective area fiber";
      }
      enum SSMF {
        description
          "Standard single mode fiber";
      }
      enum TWC {
        description
          "True wave classic";
      }
      enum TWRS {
        description
          "True wave reduced slope";
      }
    }
  }


  // grouping statements
  grouping otdr-fiber-profile {
    description
      "Enclosing container for otdr fiber-profile configuration";
    leaf refractive-index {
      type decimal64 {
        fraction-digits 6;
        range "1.400000..1.700000";
      }
      default "1.467900";
      description
        "refractive ratio";
    }
    leaf backscatter-index {
     type decimal64 {
       fraction-digits 2;
     }
     description
       "backscatter ratio";
    }
    leaf reflectance-threshold {
       type decimal64 {
         fraction-digits 2;
         range "-65.0..-14.0";
       }
       default "-40";
       description
         "reflection threshold";
    }
    leaf splice-loss-thr {
      type decimal64 {
        fraction-digits 2;
        range "0.00..10.00";
      }
      default "2.16";
      description
        "splice loss threshold";
    }
    leaf fiber-end-threshold {
      type decimal64 {
        fraction-digits 2;
        range "1..65";
      }
      default "3";
      description
        "fiber end event threshold";
    }
  }

  grouping event {
    leaf event-type {
      type otdr-event-type;
      description
        "OTDR event type";
    }
    leaf distance-m {
      type uint32;
      units "m";
      description
          "Distance at which the event occurred in meters.";
    }
    leaf loss-db {
      type decimal64 {
        fraction-digits 2;
      }
      units "dB";
      description
        "The fiber loss that occurred at the event in dB.";
    }
    leaf reflection-db {
      type decimal64 {
        fraction-digits 2;
      }
      units "dB";
      description
        "The reflection that occurred at the event in dB.";
    }
  }

  grouping otdr-trace {
    leaf total-length-m {
      type uint32;
      units "m";
      description
        "Total measured length of the fiber in meters.";
    }
    leaf total-loss-db {
      type decimal64 {
        fraction-digits 2;
      }
      units "dB";
      description
        "Total measured loss of the fiber.";
    }
    leaf optical-return-loss-db {
      type decimal64 {
        fraction-digits 2;
      }
      units "dB";
      description
        "Optical return loss of the fiber in dB.";
    }
    leaf average-loss-db-km {
      type decimal64 {
        fraction-digits 2;
      }
      units "dB";
      description
        "Optical return loss of the fiber in dB.";
    }
    leaf discovered-fiber-type {
      type fiber-type-profile;
      description
        "Discovered fiber type, if the OTDR can infer this information.";
    }
    leaf event-count {
      type uint32;
      description
       "Count of the event.";
    }
    list events {
      key "event-id";
      leaf event-id {
        type uint8;
        description
          "Event index";
      }
      uses event;
    }
  } 

  grouping otdr-configuration {
    description
      "OTDR configuration options which can be set on the device. 
       It is not required that every field be set as some fields may not apply for a given implementation";
    leaf name {
      type string;
      description
        "name of the otdr, i.e., the otdr port name";
    }
    leaf acquisition-time-s {
      type uint32 {
        range "10..180";
      }
      units "second";
      default "60";
      description
        "The time in seconds in which the OTDR trace will run continuously to collect data.";
    }
    leaf range-m {
      type uint32 {
        range "0..128000";
      }
      units "m";
      default "50";
      description
        "The maximum fiber distance range in meters that the OTDR trace will support.";
    }
    leaf pulse-width-ns {
      type uint32 {
        range "10..20000";
      }
      units "ns";
      default "3000";
      description
        "The pulse width in nanoseconds which defines how long pulses sent by the
         OTDR will be during the test.";
    }
    leaf wavelength-mhz {
      type uint64; 
      units "MHz";
      default "200000000";
      description
        "The wavelength in MHz that will be sent by the OTDR. 
         This may be left blank if the OTDR only supports one wavelength.";
    }
    leaf sample-resolution-m {
      type decimal64 {
        fraction-digits 2;
          range "0.00..160.00";
      }
      units "m";
      default "10";
      description
        "Sampling resolution in meters.";
    }
    leaf fiber-type {
      type fiber-type-profile;
      default SSMF;
      description
        "The type of fiber that is being measured.";
    }
  }

  // data definition statements
	container sonic-otdr {
    container OTDR_COMMON {
      list OTDR_COMMON_LIST {
        key "scan-type";
        max-elements 3;
        leaf scan-type {
          type otdr-scan-type;
        }
        uses otdr-configuration;
      }
    }

    container FIBER_PROFILE { 
      container DEFAULT {
        uses otdr-fiber-profile;
      }
    }
    
    container OTDR {
      list OTDR_LIST {
        key "name";
        max-elements 3;
        leaf parent-port {
          // TODO 
          type string {
            length 0..31;
          }
          /*type leafref {
            path "/oc-platform:components/oc-platform:component/" +
              "oc-platform:name";
          }*/
          description
            "Reference to system-supplied name of the port to be scaned.";
          }
        uses otdr-configuration;
        uses otdr-fiber-profile;
      }
    }
  }

  // augment statements

  // rpc statements

  // notification statements

}
