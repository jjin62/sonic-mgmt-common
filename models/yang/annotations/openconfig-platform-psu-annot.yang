module openconfig-platform-psu-annot {

    yang-version "1";
    namespace "http://openconfig.net/yang/platform-annot";
    prefix "oc-platform-annot";

    import sonic-extensions { prefix sonic-ext; }
    import openconfig-platform { prefix oc-platform; }
    import openconfig-platform-psu { prefix oc-platform-psu; }

    deviation /oc-platform:components {
      deviate add {
        sonic-ext:db-name "STATE_DB";
        sonic-ext:table-name "PSU_INFO";
      }
    }

    deviation /oc-platform:components/oc-platform:component {
      deviate add {
        sonic-ext:key-transformer "oc_name_key_xfmr";
      }
    }

    deviation /oc-platform:components/oc-platform:component/oc-platform:state {
      deviate add {
      }
    }

    deviation /oc-platform:components/oc-platform:component/oc-platform:state/oc-platform:name {
      deviate add {
        sonic-ext:field-transformer "oc_name_field_xfmr";
      }
    }

    deviation /oc-platform:components/oc-platform:component/oc-platform:state/oc-platform:type {
      deviate add {
        sonic-ext:field-name "model";
      }
    }

    deviation /oc-platform:components/oc-platform:component/oc-platform:state/oc-platform:hardware-version {
      deviate add {
        sonic-ext:field-name "revision";
      }
    }

    deviation /oc-platform:components/oc-platform:component/oc-platform:state/oc-platform:serial-no {
      deviate add {
        sonic-ext:field-name "serial";
      }
    }

    deviation /oc-platform:components/oc-platform:component/oc-platform:state/oc-platform:removable {
      deviate add {
        sonic-ext:field-name "is_replaceable";
      }
    }

    deviation /oc-platform:components/oc-platform:component/oc-platform:state/oc-platform:oper-status {
      deviate add {
        sonic-ext:field-name "status";
      }
    }

    deviation /oc-platform:components/oc-platform:component/oc-platform:state/oc-platform:status-led {
      deviate add {
        sonic-ext:field-name "led_status";
      }
    }

    deviation /oc-platform:components/oc-platform:component/oc-platform:state/oc-platform:temperature {
      deviate add {
      }
    }

    deviation /oc-platform:components/oc-platform:component/oc-platform:state/oc-platform:temperature/oc-platform:instant {
      deviate add {
        sonic-ext:field-name "temp";
      }
    }

    deviation /oc-platform:components/oc-platform:component/oc-platform:state/oc-platform:temperature/oc-platform:high-threshold {
      deviate add {
        sonic-ext:field-name "temp_threshold";
      }
    }

    deviation /oc-platform:components/oc-platform:component/oc-platform:power-supply {
      deviate add {
      }
    }

    deviation /oc-platform:components/oc-platform:component/oc-platform:power-supply/oc-platform:state {
      deviate add {
      }
    }

    deviation /oc-platform:components/oc-platform:component/oc-platform:power-supply/oc-platform:state/oc-platform-psu:enabled {
      deviate add {
        sonic-ext:field-name "presence";
      }
    }

    deviation /oc-platform:components/oc-platform:component/oc-platform:power-supply/oc-platform:state/oc-platform-psu:capacity {
      deviate add {
        sonic-ext:field-name "max_power";
      }
    }

    deviation /oc-platform:components/oc-platform:component/oc-platform:power-supply/oc-platform:state/oc-platform-psu:input-current {
      deviate add {
        sonic-ext:field-name "input_current";
      }
    }

    deviation /oc-platform:components/oc-platform:component/oc-platform:power-supply/oc-platform:state/oc-platform-psu:input-voltage {
      deviate add {
        sonic-ext:field-name "input_voltage";
      }
    }

    deviation /oc-platform:components/oc-platform:component/oc-platform:power-supply/oc-platform:state/oc-platform-psu:output-current {
      deviate add {
        sonic-ext:field-name "current";
      }
    }

    deviation /oc-platform:components/oc-platform:component/oc-platform:power-supply/oc-platform:state/oc-platform-psu:output-voltage {
      deviate add {
        sonic-ext:field-name "voltage";
      }
    }

    deviation /oc-platform:components/oc-platform:component/oc-platform:power-supply/oc-platform:state/oc-platform-psu:output-power {
      deviate add {
        sonic-ext:field-name "power";
      }
    }

}
