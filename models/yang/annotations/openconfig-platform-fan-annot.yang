module openconfig-platform-fan-annot {

    yang-version "1";
    namespace "http://openconfig.net/yang/platform-annot";
    prefix "oc-platform-annot";

    import sonic-extensions { prefix sonic-ext; }
    import openconfig-platform { prefix oc-platform; }
    import openconfig-platform-fan { prefix oc-platform-fan; }

    deviation /oc-platform:components {
      deviate add {
        sonic-ext:db-name "STATE_DB";
        sonic-ext:table-name "FAN_INFO";
      }
    }

    deviation /oc-platform:components/oc-platform:component {
      deviate add {
        sonic-ext:key-transformer "oc_name_key_xfmr";
      }
    }

    deviation /oc-platform:components/oc-platform:component/oc-platform:state {
      deviate add {
      }
    }

    deviation /oc-platform:components/oc-platform:component/oc-platform:state/oc-platform:name {
      deviate add {
        sonic-ext:field-transformer "oc_name_field_xfmr";
      }
    }

    deviation /oc-platform:components/oc-platform:component/oc-platform:state/oc-platform:type {
      deviate add {
        sonic-ext:field-name "model";
      }
    }

    deviation /oc-platform:components/oc-platform:component/oc-platform:state/oc-platform:location {
      deviate add {
        sonic-ext:field-name "drawer_name";
      }
    }

    deviation /oc-platform:components/oc-platform:component/oc-platform:state/oc-platform:hardware-version {
      deviate add {
      }
    }

    deviation /oc-platform:components/oc-platform:component/oc-platform:state/oc-platform:serial-no {
      deviate add {
        sonic-ext:field-name "serial";
      }
    }

    deviation /oc-platform:components/oc-platform:component/oc-platform:state/oc-platform:removable {
      deviate add {
        sonic-ext:field-name "is_replaceable";
      }
    }

    deviation /oc-platform:components/oc-platform:component/oc-platform:state/oc-platform:oper-status {
      deviate add {
        sonic-ext:field-name "status";
      }
    }

    deviation /oc-platform:components/oc-platform:component/oc-platform:state/oc-platform:status-led {
      deviate add {
        sonic-ext:field-name "led_status";
      }
    }

    deviation /oc-platform:components/oc-platform:component/oc-platform:fan {
      deviate add {
      }
    }

    deviation /oc-platform:components/oc-platform:component/oc-platform:fan/oc-platform:state {
      deviate add {
      }
    }

    deviation /oc-platform:components/oc-platform:component/oc-platform:fan/oc-platform:state/oc-platform-fan:speed {
      deviate add {
        sonic-ext:field-name "speed";
      }
    }

    deviation /oc-platform:components/oc-platform:component/oc-platform:fan/oc-platform:state/oc-platform-fan:target-speed {
      deviate add {
        sonic-ext:field-name "speed_target";
      }
    }

    deviation /oc-platform:components/oc-platform:component/oc-platform:fan/oc-platform:state/oc-platform-fan:direction {
      deviate add {
        sonic-ext:field-name "direction";
      }
    }

}
