module openconfig-gnoi-otdr-annot {

    yang-version "1";

    namespace "http://openconfig.net/yang/annotation/oc-gnoi-otdr-annot";
    prefix "oc-gnoi-otdr-annot";

    import openconfig-platform { prefix oc-platform; }
    import openconfig-extensions { prefix oc-ext; }
    import openconfig-optical-amplifier { prefix oc-opt-amp; }
    import openconfig-yang-types { prefix oc-yang; }
    import openconfig-gnoi-otdr { prefix oc-gnoi-otdr; }

    deviation /oc-gnoi-otdr:optical-time-domain-reflectometer {
      deviate add {
      }
    }

    deviation /oc-gnoi-otdr:optical-time-domain-reflectometer/oc-gnoi-otdr:otdrs {
      deviate add {
      }
    }

    deviation /oc-gnoi-otdr:optical-time-domain-reflectometer/oc-gnoi-otdr:otdrs/oc-gnoi-otdr:otdr {
      deviate add {
        sonic-ext:table-name "OTDR";
        sonic-ext:key-transformer "oc_name_key_xfmr";
      }
    }

    deviation /oc-gnoi-otdr:optical-time-domain-reflectometer/oc-gnoi-otdr:otdrs/oc-gnoi-otdr:otdr/oc-gnoi-otdr:config {
      deviate add {
      }
    }

    deviation /oc-gnoi-otdr:optical-time-domain-reflectometer/oc-gnoi-otdr:otdrs/oc-gnoi-otdr:otdr/oc-gnoi-otdr:config/oc-gnoi-otdr:reflectance-threshold {
      deviate add {
        sonic-ext:field-name "reflectance-threshold";
      }
    }

    deviation /oc-gnoi-otdr:optical-time-domain-reflectometer/oc-gnoi-otdr:otdrs/oc-gnoi-otdr:otdr/oc-gnoi-otdr:config/oc-gnoi-otdr:backscatter-index {
      deviate add {
        sonic-ext:field-name "backscatter-index";
      }
    }

    deviation /oc-gnoi-otdr:optical-time-domain-reflectometer/oc-gnoi-otdr:otdrs/oc-gnoi-otdr:otdr/oc-gnoi-otdr:config/oc-gnoi-otdr:splice-loss-threshold {
      deviate add {
        sonic-ext:field-name "splice-loss-threshold";
      }
    }

    deviation /oc-gnoi-otdr:optical-time-domain-reflectometer/oc-gnoi-otdr:otdrs/oc-gnoi-otdr:otdr/oc-gnoi-otdr:config/oc-gnoi-otdr:refractive-index {
      deviate add {
        sonic-ext:field-name "refractive-index";
      }
    }

    deviation /oc-gnoi-otdr:optical-time-domain-reflectometer/oc-gnoi-otdr:otdrs/oc-gnoi-otdr:otdr/oc-gnoi-otdr:config/oc-gnoi-otdr:fiber-end-threshold {
      deviate add {
        sonic-ext:field-name "fiber-end-threshold";
      }
    }

    deviation /oc-gnoi-otdr:optical-time-domain-reflectometer/oc-gnoi-otdr:otdrs/oc-gnoi-otdr:otdr/oc-gnoi-otdr:config/oc-gnoi-otdr:fiber-type {
      deviate add {
        sonic-ext:field-name "fiber-type";
      }
    }

    deviation /oc-gnoi-otdr:optical-time-domain-reflectometer/oc-gnoi-otdr:otdrs/oc-gnoi-otdr:otdr/oc-gnoi-otdr:config/oc-gnoi-otdr:range-m {
      deviate add {
        sonic-ext:field-name "range-m";
      }
    }

    deviation /oc-gnoi-otdr:optical-time-domain-reflectometer/oc-gnoi-otdr:otdrs/oc-gnoi-otdr:otdr/oc-gnoi-otdr:config/oc-gnoi-otdr:acquisition-time-s {
      deviate add {
        sonic-ext:field-name "acquisition-time-s";
      }
    }

    deviation /oc-gnoi-otdr:optical-time-domain-reflectometer/oc-gnoi-otdr:otdrs/oc-gnoi-otdr:otdr/oc-gnoi-otdr:config/oc-gnoi-otdr:sampling-resolution-m {
      deviate add {
        sonic-ext:field-name "sampling-resolution-m";
      }
    }

    deviation /oc-gnoi-otdr:optical-time-domain-reflectometer/oc-gnoi-otdr:otdrs/oc-gnoi-otdr:otdr/oc-gnoi-otdr:config/oc-gnoi-otdr:wavelength-mhz {
      deviate add {
        sonic-ext:field-name "wavelength-mhz";
      }
    }

    deviation /oc-gnoi-otdr:optical-time-domain-reflectometer/oc-gnoi-otdr:otdrs/oc-gnoi-otdr:otdr/oc-gnoi-otdr:config/oc-gnoi-otdr:name {
      deviate add {
        sonic-ext:field-transformer "oc_name_field_xfmr";
      }
    }

    deviation /oc-gnoi-otdr:optical-time-domain-reflectometer/oc-gnoi-otdr:otdrs/oc-gnoi-otdr:otdr/oc-gnoi-otdr:config/oc-gnoi-otdr:pulse-width-ns {
      deviate add {
        sonic-ext:field-name "pulse-width-ns";
      }
    }

    deviation /oc-gnoi-otdr:optical-time-domain-reflectometer/oc-gnoi-otdr:otdrs/oc-gnoi-otdr:otdr/oc-gnoi-otdr:state {
      deviate add {
        sonic-ext:db-name "STATE_DB";
        sonic-ext:table-name "OTDR_TABLE";
        sonic-ext:key-transformer "oc_name_key_xfmr";
      }
    }

    deviation /oc-gnoi-otdr:optical-time-domain-reflectometer/oc-gnoi-otdr:otdrs/oc-gnoi-otdr:otdr/oc-gnoi-otdr:state/oc-gnoi-otdr:sample-resolution-m {
      deviate add {
        sonic-ext:field-name "sample-resolution-m";
      }
    }

    deviation /oc-gnoi-otdr:optical-time-domain-reflectometer/oc-gnoi-otdr:otdrs/oc-gnoi-otdr:otdr/oc-gnoi-otdr:state/oc-gnoi-otdr:backscatter-index {
      deviate add {
        sonic-ext:field-name "backscatter-index";
      }
    }

    deviation /oc-gnoi-otdr:optical-time-domain-reflectometer/oc-gnoi-otdr:otdrs/oc-gnoi-otdr:otdr/oc-gnoi-otdr:state/oc-gnoi-otdr:pulse-width-ns {
      deviate add {
        sonic-ext:field-name "pulse-width-ns";
      }
    }

    deviation /oc-gnoi-otdr:optical-time-domain-reflectometer/oc-gnoi-otdr:otdrs/oc-gnoi-otdr:otdr/oc-gnoi-otdr:state/oc-gnoi-otdr:fiber-type {
      deviate add {
        sonic-ext:field-name "fiber-type";
      }
    }

    deviation /oc-gnoi-otdr:optical-time-domain-reflectometer/oc-gnoi-otdr:otdrs/oc-gnoi-otdr:otdr/oc-gnoi-otdr:state/oc-gnoi-otdr:name {
      deviate add {
        sonic-ext:field-transformer "oc_name_field_xfmr";
      }
    }

    deviation /oc-gnoi-otdr:optical-time-domain-reflectometer/oc-gnoi-otdr:otdrs/oc-gnoi-otdr:otdr/oc-gnoi-otdr:state/oc-gnoi-otdr:range-m {
      deviate add {
        sonic-ext:field-name "range-m";
      }
    }

    deviation /oc-gnoi-otdr:optical-time-domain-reflectometer/oc-gnoi-otdr:otdrs/oc-gnoi-otdr:otdr/oc-gnoi-otdr:state/oc-gnoi-otdr:reflectance-threshold {
      deviate add {
        sonic-ext:field-name "reflectance-threshold";
      }
    }

    deviation /oc-gnoi-otdr:optical-time-domain-reflectometer/oc-gnoi-otdr:otdrs/oc-gnoi-otdr:otdr/oc-gnoi-otdr:state/oc-gnoi-otdr:splice-loss-threshold {
      deviate add {
        sonic-ext:field-name "splice-loss-threshold";
      }
    }

    deviation /oc-gnoi-otdr:optical-time-domain-reflectometer/oc-gnoi-otdr:otdrs/oc-gnoi-otdr:otdr/oc-gnoi-otdr:state/oc-gnoi-otdr:status {
      deviate add {
        sonic-ext:field-name "status";
      }
    }

    deviation /oc-gnoi-otdr:optical-time-domain-reflectometer/oc-gnoi-otdr:otdrs/oc-gnoi-otdr:otdr/oc-gnoi-otdr:state/oc-gnoi-otdr:wavelength-mhz {
      deviate add {
        sonic-ext:field-name "wavelength-mhz";
      }
    }

    deviation /oc-gnoi-otdr:optical-time-domain-reflectometer/oc-gnoi-otdr:otdrs/oc-gnoi-otdr:otdr/oc-gnoi-otdr:state/oc-gnoi-otdr:fiber-end-threshold {
      deviate add {
        sonic-ext:field-name "fiber-end-threshold";
      }
    }

    deviation /oc-gnoi-otdr:optical-time-domain-reflectometer/oc-gnoi-otdr:otdrs/oc-gnoi-otdr:otdr/oc-gnoi-otdr:state/oc-gnoi-otdr:refractive-index {
      deviate add {
        sonic-ext:field-name "refractive-index";
      }
    }

    deviation /oc-gnoi-otdr:optical-time-domain-reflectometer/oc-gnoi-otdr:otdrs/oc-gnoi-otdr:otdr/oc-gnoi-otdr:state/oc-gnoi-otdr:acquisition-time-s {
      deviate add {
        sonic-ext:field-name "acquisition-time-s";
      }
    }

    deviation /oc-gnoi-otdr:optical-time-domain-reflectometer/oc-gnoi-otdr:otdrs/oc-gnoi-otdr:otdr/oc-gnoi-otdr:scan-results {
      deviate add {
        sonic-ext:db-name "STATE_DB";
      }
    }

    deviation /oc-gnoi-otdr:optical-time-domain-reflectometer/oc-gnoi-otdr:otdrs/oc-gnoi-otdr:otdr/oc-gnoi-otdr:scan-results/oc-gnoi-otdr:traces {
      deviate add {
        sonic-ext:table-name "OTDR_RESULT";
        sonic-ext:key-transformer "otdr_result_key_xfmr";
      }
    }

    deviation /oc-gnoi-otdr:optical-time-domain-reflectometer/oc-gnoi-otdr:otdrs/oc-gnoi-otdr:otdr/oc-gnoi-otdr:scan-results/oc-gnoi-otdr:traces/oc-gnoi-otdr:discovered-fiber-type {
      deviate add {
        sonic-ext:field-name "discovered-fiber-type";
      }
    }

    deviation /oc-gnoi-otdr:optical-time-domain-reflectometer/oc-gnoi-otdr:otdrs/oc-gnoi-otdr:otdr/oc-gnoi-otdr:scan-results/oc-gnoi-otdr:traces/oc-gnoi-otdr:events {
      deviate add {
        sonic-ext:table-name "OTDR_EVENT";
        sonic-ext:key-transformer "otdr_event_key_xfmr";
      }
    }

    deviation /oc-gnoi-otdr:optical-time-domain-reflectometer/oc-gnoi-otdr:otdrs/oc-gnoi-otdr:otdr/oc-gnoi-otdr:scan-results/oc-gnoi-otdr:traces/oc-gnoi-otdr:events/oc-gnoi-otdr:reflection-db {
      deviate add {
        sonic-ext:field-name "reflection-db";
      }
    }

    deviation /oc-gnoi-otdr:optical-time-domain-reflectometer/oc-gnoi-otdr:otdrs/oc-gnoi-otdr:otdr/oc-gnoi-otdr:scan-results/oc-gnoi-otdr:traces/oc-gnoi-otdr:events/oc-gnoi-otdr:event-type {
      deviate add {
        sonic-ext:field-name "event-type";
      }
    }

    deviation /oc-gnoi-otdr:optical-time-domain-reflectometer/oc-gnoi-otdr:otdrs/oc-gnoi-otdr:otdr/oc-gnoi-otdr:scan-results/oc-gnoi-otdr:traces/oc-gnoi-otdr:events/oc-gnoi-otdr:event-id {
      deviate add {
        sonic-ext:field-transformer "otdr_event_type_field_xfmr";
      }
    }

    deviation /oc-gnoi-otdr:optical-time-domain-reflectometer/oc-gnoi-otdr:otdrs/oc-gnoi-otdr:otdr/oc-gnoi-otdr:scan-results/oc-gnoi-otdr:traces/oc-gnoi-otdr:events/oc-gnoi-otdr:distance-m {
      deviate add {
        sonic-ext:field-name "distance-m";
      }
    }

    deviation /oc-gnoi-otdr:optical-time-domain-reflectometer/oc-gnoi-otdr:otdrs/oc-gnoi-otdr:otdr/oc-gnoi-otdr:scan-results/oc-gnoi-otdr:traces/oc-gnoi-otdr:events/oc-gnoi-otdr:loss-db {
      deviate add {
        sonic-ext:field-name "loss-db";
      }
    }

    deviation /oc-gnoi-otdr:optical-time-domain-reflectometer/oc-gnoi-otdr:otdrs/oc-gnoi-otdr:otdr/oc-gnoi-otdr:scan-results/oc-gnoi-otdr:traces/oc-gnoi-otdr:average-loss-db-km {
      deviate add {
        sonic-ext:field-name "average-loss-db-km";
      }
    }

    deviation /oc-gnoi-otdr:optical-time-domain-reflectometer/oc-gnoi-otdr:otdrs/oc-gnoi-otdr:otdr/oc-gnoi-otdr:scan-results/oc-gnoi-otdr:traces/oc-gnoi-otdr:completion-time {
      deviate add {
        sonic-ext:field-transformer "otdr_completion_time_field_xfmr";
      }
    }

    deviation /oc-gnoi-otdr:optical-time-domain-reflectometer/oc-gnoi-otdr:otdrs/oc-gnoi-otdr:otdr/oc-gnoi-otdr:scan-results/oc-gnoi-otdr:traces/oc-gnoi-otdr:event-count {
      deviate add {
        sonic-ext:field-name "event-count";
      }
    }

    deviation /oc-gnoi-otdr:optical-time-domain-reflectometer/oc-gnoi-otdr:otdrs/oc-gnoi-otdr:otdr/oc-gnoi-otdr:scan-results/oc-gnoi-otdr:traces/oc-gnoi-otdr:sor-file {
      deviate add {
        sonic-ext:field-name "sor-file";
      }
    }

    deviation /oc-gnoi-otdr:optical-time-domain-reflectometer/oc-gnoi-otdr:otdrs/oc-gnoi-otdr:otdr/oc-gnoi-otdr:scan-results/oc-gnoi-otdr:traces/oc-gnoi-otdr:total-length-m {
      deviate add {
        sonic-ext:field-name "total-length-m";
      }
    }

    deviation /oc-gnoi-otdr:optical-time-domain-reflectometer/oc-gnoi-otdr:otdrs/oc-gnoi-otdr:otdr/oc-gnoi-otdr:scan-results/oc-gnoi-otdr:traces/oc-gnoi-otdr:total-loss-db {
      deviate add {
        sonic-ext:field-name "total-loss-db";
      }
    }

    deviation /oc-gnoi-otdr:optical-time-domain-reflectometer/oc-gnoi-otdr:otdrs/oc-gnoi-otdr:otdr/oc-gnoi-otdr:scan-results/oc-gnoi-otdr:traces/oc-gnoi-otdr:optical-return-loss-db {
      deviate add {
        sonic-ext:field-name "optical-return-loss-db";
      }
    }

    deviation /oc-gnoi-otdr:optical-time-domain-reflectometer/oc-gnoi-otdr:otdrs/oc-gnoi-otdr:otdr/oc-gnoi-otdr:scan-results/oc-gnoi-otdr:traces/oc-gnoi-otdr:baseline {
      deviate add {
        sonic-ext:field-name "baseline";
      }
    }

    deviation /oc-gnoi-otdr:optical-time-domain-reflectometer/oc-gnoi-otdr:otdrs/oc-gnoi-otdr:otdr/oc-gnoi-otdr:name {
      deviate add {
        //sonic-ext:field-transformer "oc_name_field_xfmr";
      }
    }

    deviation /oc-gnoi-otdr:optical-time-domain-reflectometer/oc-gnoi-otdr:otdrs/oc-gnoi-otdr:otdr/oc-gnoi-otdr:parent-port {
      deviate add {
        sonic-ext:field-name "oc_name_field_xfmr";
      }
    }

    deviation /oc-gnoi-otdr:optical-time-domain-reflectometer/oc-gnoi-otdr:config-common {
      deviate add {
        sonic-ext:table-name "OTDR-COMMON";
      }
    }

    deviation /oc-gnoi-otdr:optical-time-domain-reflectometer/oc-gnoi-otdr:config-common/oc-gnoi-otdr:scan-types {
      deviate add {
        sonic-ext:key-transformer "otdr_scan_type_key_xfmr";
      }
    }

    deviation /oc-gnoi-otdr:optical-time-domain-reflectometer/oc-gnoi-otdr:config-common/oc-gnoi-otdr:scan-types/oc-gnoi-otdr:wavelength-mhz {
      deviate add {
        sonic-ext:field-name "wavelength-mhz";
      }
    }

    deviation /oc-gnoi-otdr:optical-time-domain-reflectometer/oc-gnoi-otdr:config-common/oc-gnoi-otdr:scan-types/oc-gnoi-otdr:sample-resolution-m {
      deviate add {
        sonic-ext:field-name "sample-resolution-m";
      }
    }

    deviation /oc-gnoi-otdr:optical-time-domain-reflectometer/oc-gnoi-otdr:config-common/oc-gnoi-otdr:scan-types/oc-gnoi-otdr:scan-type {
      deviate add {
        sonic-ext:field-transformer "otdr_scan_type_field_xfmr";
      }
    }

    deviation /oc-gnoi-otdr:optical-time-domain-reflectometer/oc-gnoi-otdr:config-common/oc-gnoi-otdr:scan-types/oc-gnoi-otdr:fiber-type {
      deviate add {
        sonic-ext:field-name "fiber-type";
      }
    }

    deviation /oc-gnoi-otdr:optical-time-domain-reflectometer/oc-gnoi-otdr:config-common/oc-gnoi-otdr:scan-types/oc-gnoi-otdr:name {
      deviate add {
        sonic-ext:field-name "name";
      }
    }

    deviation /oc-gnoi-otdr:optical-time-domain-reflectometer/oc-gnoi-otdr:config-common/oc-gnoi-otdr:scan-types/oc-gnoi-otdr:acquisition-time-s {
      deviate add {
        sonic-ext:field-name "acquisition-time-s";
      }
    }

    deviation /oc-gnoi-otdr:optical-time-domain-reflectometer/oc-gnoi-otdr:config-common/oc-gnoi-otdr:scan-types/oc-gnoi-otdr:range-m {
      deviate add {
        sonic-ext:field-name "range-m";
      }
    }

    deviation /oc-gnoi-otdr:optical-time-domain-reflectometer/oc-gnoi-otdr:config-common/oc-gnoi-otdr:scan-types/oc-gnoi-otdr:pulse-width-ns {
      deviate add {
        sonic-ext:field-name "pulse-width-ns";
      }
    }

    deviation /oc-gnoi-otdr:optical-time-domain-reflectometer/oc-gnoi-otdr:config-common/oc-gnoi-otdr:fiber-profile {
      deviate add {
        sonic-ext:table-name "FIBER_PROFILE";
        sonic-ext:key-name "DEFAULT";
      }
    }

    deviation /oc-gnoi-otdr:optical-time-domain-reflectometer/oc-gnoi-otdr:config-common/oc-gnoi-otdr:fiber-profile/oc-gnoi-otdr:reflectance-threshold {
      deviate add {
        sonic-ext:field-name "reflectance-threshold";
      }
    }

    deviation /oc-gnoi-otdr:optical-time-domain-reflectometer/oc-gnoi-otdr:config-common/oc-gnoi-otdr:fiber-profile/oc-gnoi-otdr:splice-loss-threshold {
      deviate add {
        sonic-ext:field-name "splice-loss-threshold";
      }
    }

    deviation /oc-gnoi-otdr:optical-time-domain-reflectometer/oc-gnoi-otdr:config-common/oc-gnoi-otdr:fiber-profile/oc-gnoi-otdr:fiber-end-threshold {
      deviate add {
        sonic-ext:field-name "fiber-end-threshold";
      }
    }

    deviation /oc-gnoi-otdr:optical-time-domain-reflectometer/oc-gnoi-otdr:config-common/oc-gnoi-otdr:fiber-profile/oc-gnoi-otdr:refractive-index {
      deviate add {
        sonic-ext:field-name "refractive-index";
      }
    }

    deviation /oc-gnoi-otdr:optical-time-domain-reflectometer/oc-gnoi-otdr:config-common/oc-gnoi-otdr:fiber-profile/oc-gnoi-otdr:backscatter-index {
      deviate add {
        sonic-ext:field-name "backscatter-index";
      }
    }

    deviation /oc-gnoi-otdr:otdr-scan {
      deviate add {
        sonic-ext:rpc-callback "rpc_otdr_scan_cb";
      }
    }

}
